FME workspace MakeAttribute.fmw

Parameters:
- DestDataset_TEXTLINE =
- DestDataset_TEXTLINE_5 =
- DestDataset_TEXTLINE_6 =
- DestDataset_TEXTLINE_7 =
- SourceDataset_GEOTIFF =
- SourceDataset_GEOTIFF_3 =
- SourceDataset_PNGRASTER =
- SourceDataset_PNGRASTER_4 =
- SourceDataset_PNGRASTER_5 =

Readers:
- GEOTIFF_1: GEOTIFF from $(SourceDataset_GEOTIFF)
- PNGRASTER_1: PNGRASTER from $(SourceDataset_PNGRASTER)
- PNGRASTER_2: PNGRASTER from $(SourceDataset_PNGRASTER_5)
- PNGRASTER_3: PNGRASTER from $(SourceDataset_PNGRASTER_4)
- GEOTIFF_2: GEOTIFF from $(SourceDataset_GEOTIFF_3)

Writers:
- TEXTLINE_1: TEXTLINE to $(DestDataset_TEXTLINE_5)
- TEXTLINE_2: TEXTLINE to $(DestDataset_TEXTLINE)
- TEXTLINE_3: TEXTLINE to $(DestDataset_TEXTLINE_7)
- TEXTLINE_4: TEXTLINE to $(DestDataset_TEXTLINE_6)

PNGRASTER (reader PNGRASTER_2)
PNGRASTER (reader PNGRASTER_3)
    -> text_line (writer TEXTLINE_4)
text_line (writer TEXTLINE_4)
    attributes: text_line_data buffer
GEOTIFF (reader GEOTIFF_2)
    -> RasterToPolygonCoercer
RasterToPolygonCoercer
    EXTRACT_NODATA = No
    LABEL_ATTRIBUTE = _label
    PRESERVE_ATTRIBUTES = Yes
    POLYGONS -> CenterPointExtractor
CenterPointExtractor
    CENTX = _inside_x
    CENTY = _inside_y
    CENTZ = _inside_z
    EXTRACTIONMODE = CENTER
    -> BoundsExtractor
BoundsExtractor
    XMAX = _xmax
    XMIN = _xmin
    YMAX = _ymax
    YMIN = _ymin
    ZMAX = _zmax
    ZMIN = _zmin
    -> ExpressionEvaluator
ExpressionEvaluator
    ACTION = Overwrite Existing Attributes
    ATTRLIST = _ymin
    EXPRESSION = "@Value(_ymin)*(-1)\n"
    -> ExpressionEvaluator_2
ExpressionEvaluator_2
    ACTION = Overwrite Existing Attributes
    ATTRLIST = _ymax
    EXPRESSION = @Value(_ymax)*(-1)
    -> ExpressionEvaluator_3
ExpressionEvaluator_3
    ACTION = Create New Attribute
    EXPRESSION = @Value(_xmax)-@Value(_xmin)
    VAL_ATTR = _dx
    -> ExpressionEvaluator_4
ExpressionEvaluator_4
    ACTION = Create New Attribute
    EXPRESSION = @Value(_ymin)-@Value(_ymax)
    VAL_ATTR = _dy
    -> text_line (writer TEXTLINE_1)
text_line (writer TEXTLINE_1)
    attributes: text_line_data buffer
GEOTIFF (reader GEOTIFF_1)
PNGRASTER (reader PNGRASTER_1)
    -> text_line (writer TEXTLINE_2)
text_line (writer TEXTLINE_2)
    attributes: text_line_data buffer
FeatureMerger
    ATTR_ACCUM_MODE = Merge Supplier
    ATTR_CONFLICT_RES = Use Requestor
    IGNORE_NULLS = No
    JOIN_KEYS = @Value(fme_basename) @Value(fme_basename) AUTO
    MERGE_TYPE = Attributes Only
    PROCESS_DUPS = NO
    REJECT_NULL_MISSING_KEYS = No
    SUPPLIERS_FIRST = No
text_line (writer TEXTLINE_3)
    attributes: text_line_data buffer
Counter
    CNT_ATTR = _count
    DOMAIN = counter
    SCOPE = Global
    START = 0
