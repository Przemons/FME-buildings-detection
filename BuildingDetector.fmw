FME workspace BuildingDetector.fmw

Parameters:
- DestDataset_GEOTIFF =
- DestDataset_GEOTIFF_3 =
- SourceDataset_PNGRASTER =

Readers:
- PNGRASTER_1: PNGRASTER from $(SourceDataset_PNGRASTER)

Writers:
- GEOTIFF_1: GEOTIFF to $(DestDataset_GEOTIFF)
- GEOTIFF_2: GEOTIFF to $(DestDataset_GEOTIFF_3)

PNGRASTER (reader PNGRASTER_1)
    -> Counter
Counter
    CNT_ATTR = _count
    DOMAIN = counter
    SCOPE = Global
    START = 0
    -> FeatureMerger [REQUESTOR]
    -> RasterObjectDetector
Creator
    GEOMTYPE = Geometry Object
    NUM = 1
    CREATED -> RasterObjectDetectorSamplePreparer
RasterObjectDetectorSamplePreparer
    negative_samples_dir = geoneg
    negative_samples_reuse = Use Existing
    out_bg_desc_fname = bggeo.txt
    out_vec_fname = geovec.vec
    positive_annotation_file = $(FME_MF_DIR)anno2.txt
    positive_samples_height = 200
    positive_samples_num = 2390
    positive_samples_width = 200
    -> RasterObjectDetectionModelTrainer
RasterObjectDetectionModelTrainer
    bg_desc_file = @Value(_out_bg_desc_fname)
    boosted_classifier_type = GAB
    break_value = -1
    cascade_dir_name = train.xml
    feature_type = HAAR
    haar_like_mode = BASIC
    max_depth_of_weak_tree = 1
    max_false_alarm_rate = 0.5
    max_weak_tree_count = 100
    min_hit_rate = 0.995
    num_neg_samples = @Value(_out_num_negative_samples)
    num_pos_samples = @Value(_out_pos_positive_samples)
    num_stages = 20
    out_detection_model_name = trainfolder
    positive_vec_file = @Value(_out_vec_fname)
    precalc_idx_buffer = 1024
    precalc_val_buffer = 1024
    sample_height = 24
    sample_width = 24
    weight_trim_rate = 0.95
    -> RasterObjectDetector
RasterObjectDetector
    DEST_ATTR = _detected_object_type
    DETECTION_TYPE = Custom
    DET_SUB_TYPE_CUSTOM = @Value(_out_detection_model_name)
    MAX_SIZE_HEIGHT = 300
    MAX_SIZE_WIDTH = 300
    MIN_NUM_NEIGHBOR = 2
    MIN_SIZE_HEIGHT = 100
    MIN_SIZE_WIDTH = 100
    OBJ_SIZE_UNITS = Pixels
    PRESERVE_ATTRIBUTES = Yes
    SCALE_FACTOR = 3
    DETECTED -> Junction_3
Junction_3
    -> MapnikRasterizer [Sign]
    -> FeatureMerger [SUPPLIER]
FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(_count) @Value(_count) AUTO
    MERGE_TYPE = Attributes Only
    PROCESS_DUPS = YES
    REJECT_NULL_MISSING_KEYS = No
    SUPPLIERS_FIRST = No
    MERGED -> MapnikRasterizer [Raster]
MapnikRasterizer
    BACKGROUND_COLOR = 1,1,1
    BACKGROUND_COLOR_ALPHA = 1.0
    COLROW_OR_SPACING = Spacing
    GROUP_BY = fme_basename
    INTERPRETATION_TYPE = RGBA32
    LAYER_CARDINALITY = Each rendering rule is a layer
    MAPNIK_CONFIG = Raster;raster;"__ignore__raster-properties-group;;opacity;1;scaling;near;__ignore__comp-group;;comp-op;src-over";Sign;line;"__ignore__color-group;;stroke;1,0,0;stroke-opacity;1;__ignore__line-style-group;;stroke-width;2;stroke-linejoin;miter;stroke-linecap;butt;stroke-dasharray;;stroke-miterlimit;4;__ignore__positioning-group;;offset;0;__ignore__smoothing-group;;stroke-gamma;1;stroke-gamma-method;power;smooth;0;rasterizer;full;__ignore__comp-group;;comp-op;src-over"
    SPACING = 1
    SPECIFY_GROUND_EXTENTS = Use input data ground extents
    RASTER -> PNGRASTER (writer GEOTIFF_2)
PNGRASTER (writer GEOTIFF_2)
